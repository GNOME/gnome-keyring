XDG { }

DEFINITIONS EXPLICIT TAGS ::=

BEGIN

-- This file contains definitions for keyring

TrustLevel ::= ENUMERATED {
	unknown              (0),
	untrusted            (1),
	trusted              (3),
	trustedAnchor        (4)
}

TrustAssertion ::= SEQUENCE {
	purpose                 OCTET STRING,
	level                   TrustLevel,
	peer                    OCTET STRING,

	additions               SEQUENCE OF ANY
}

TrustAssertions ::= SEQUENCE OF TrustAssertion

CertReference ::= SEQUENCE {
	serialNumber            INTEGER,
	issuer                  ANY,
	subject                 ANY OPTIONAL,

	additions               SEQUENCE OF ANY
}

TrustReference ::= CHOICE {
	certReference           [0] CertReference,
	certComplete            [1] ANY,

	additions               [2] ANY
}

trust-1 ::= SEQUENCE {
	reference               TrustReference,
	assertions              TrustAssertions,

	additions               SEQUENCE OF ANY
}

END
