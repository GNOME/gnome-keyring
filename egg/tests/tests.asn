TESTS { }

DEFINITIONS EXPLICIT TAGS ::=

BEGIN

TestInteger ::= INTEGER

TestBoolean ::= BOOLEAN

TestOctetString ::= OCTET STRING

TestGeneralized ::= GeneralizedTime

TestImplicit ::= [5] IMPLICIT OCTET STRING

TestExplicit ::= [5] EXPLICIT OCTET STRING

END
