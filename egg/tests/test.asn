TESTS { }

DEFINITIONS EXPLICIT TAGS ::=

BEGIN

TestInteger ::= INTEGER

TestBoolean ::= BOOLEAN

TestNull ::= NULL

TestAny ::= ANY

TestOctetString ::= OCTET STRING

TestGeneralized ::= GeneralizedTime

TestImplicit ::= [5] IMPLICIT OCTET STRING

TestExplicit ::= [5] EXPLICIT OCTET STRING

TestUniversal ::= [UNIVERSAL 5] IMPLICIT OCTET STRING

TestBitString ::= BIT STRING

TestIntegers ::= SEQUENCE {
	uint1                   INTEGER,
	uint2			INTEGER,
	uint3			INTEGER
}

TestData ::= SEQUENCE {
	data                    OCTET STRING
}

TestBooleanSeq ::= SEQUENCE {
	boolean                 BOOLEAN DEFAULT FALSE,
	boolean2                BOOLEAN
}

TestOid ::= SEQUENCE {
	oid                     OBJECT IDENTIFIER
}

TestAnySeq ::= SEQUENCE {
	contents                ANY
}

TestAnyExp ::= SEQUENCE {
	contents                [89] ANY
}

TestAnyChoice ::= CHOICE {
	choiceShortTag          [30] ANY,
	choiceLongTag           [31] ANY
}

TestSeqOf ::= SEQUENCE OF INTEGER

TestSetOf ::= SET OF INTEGER

TestEnumerated ::= ENUMERATED {
	valueZero         (0),
	valueOne          (1),
	valueTwo          (2),
	valueThree        (3)
}

END
